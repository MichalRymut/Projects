customPropertySet = ThisDoc.Document.PropertySets.Item("Inventor User Defined Properties")

Dim Nr_fasady As String
Dim Nr_elementu As String
Dim Nr_katalogowy As String
Dim Długość As String
Dim Kolor As String



Dim oVals1 As New List(Of String)
		oVals1.AddRange({"Część", "Złożenie"})
		oChosen = InputListBox("Wybierz Typ elementu:", oVals1, "", "Potrzebne informacje")
   
					If oChosen = "Część" Then

'Nr_fasady = InputBox("Proszę wpisać Nr fasady:", "Potrzebne informacje", "")
Nr_fasady = "ER-2_2.5(A)"
Nr_elementu = InputBox("Proszę wpisać Nr elementu: (Nazwę złożenia, do którego część przynależy np. RL-01)", "Potrzebne informacje", "")

Dim oVals2 As New List(Of String)
		oVals2.AddRange({"Corten", "Szary-O", "Szary-R", "Brak"})
		Kolor = InputListBox("Wybierz kolor:", oVals2, "", "Potrzebne informacje")
		
Dim iprop(3) As String
iprop(1) = "Kod elementu"
iprop(2) = "Długość"
iprop(3) = "Kolor"

For k = 1 To 3
Dim prop(k) As String
    Try
        prop(k) = iProperties.Value("Custom", iprop(k))
    Catch
        'Assume error means not found
        customPropertySet.Add("", iprop(k))
        iProperties.Value("Custom", iprop(k)) = "null"
    End Try
Next


For j = 1 To 1
    Dim var(j) As String
    If iProperties.Value("Custom", iprop(j)) = "null" Then
	question = MessageBox.Show("Nr katalogowy nie został określony, czy chcesz określić?", "IProperty nie określone", MessageBoxButtons.YesNo, MessageBoxIcon.Question, MessageBoxDefaultButton.Button1)
					If question = vbYes Then
        var(j) = InputBox("Proszę wpisać Nr katalogowy:", "Warning", "")
        iProperties.Value("Custom", iprop(j)) = var(j)
					End If
	Else
		var(j) = iProperties.Value("Custom", iprop(j))
    End If
	
Next

For j = 2 To 2
    Dim var(j) As String
    If iProperties.Value("Custom", iprop(j)) = "null" Then
	question = MessageBox.Show("Długość nie została określona, czy chcesz określić?", "IProperty nie określone", MessageBoxButtons.YesNo, MessageBoxIcon.Question, MessageBoxDefaultButton.Button1)
					If question = vbYes Then
        var(j) = InputBox("Proszę wpisać wartość dla długości:" & iprop(j), "Warning", "")
        iProperties.Value("Custom", iprop(j)) = var(j)
					End If
	Else
		var(j) = iProperties.Value("Custom", iprop(j))
    End If
	
Next


For j = 3 To 3
    Dim var(j) As String
	If Kolor = "Corten"
	
        var(j) = "Kolor O1 corten – proszek JOTUN 2901.I584.21 PM SD 2901 (Class 2)"
        iProperties.Value("Custom", iprop(j)) = var(j)
	End If
	If Kolor = "Szary-O"
	
        var(j) = "Kolor O2 szary - proszek JOTUN SD 2901 Product Code: 1043410 (class 2)"
        iProperties.Value("Custom", iprop(j)) = var(j)
	End If
	If Kolor = "Szary-R"
	
        var(j) = "Kolor R1 szary – proszek JOTUN 2901.I182.19PM SD 2901 (class 2)"
        iProperties.Value("Custom", iprop(j)) = var(j)
	End If
	If Kolor = "Brak"
	
        var(j) = " "
        iProperties.Value("Custom", iprop(j)) = var(j)
	End If
 Next




Nr_katalogowy = iProperties.Value("Custom", iprop(1))
Długość = iProperties.Value("Custom", iprop(2))

If Nr_elementu = ""
	
	If Kolor = "Brak"
	
	Dim Name As String
Name = ThisDoc.Path & "\" & Nr_fasady & "_" & Nr_katalogowy & "_" & Długość & ".ipt"
ThisDoc.Document.SaveAs(Name, True)
	Else
		
	Dim Name As String
Name = ThisDoc.Path & "\" & Nr_fasady & "_" & Nr_katalogowy & "_" & Długość & "_" & Kolor & ".ipt"
ThisDoc.Document.SaveAs(Name, True)

End If
	
Else
	
	If Kolor = "Brak"
	
	Dim Name As String
Name = ThisDoc.Path & "\" & Nr_fasady & "_" & Nr_elementu & "_" & Nr_katalogowy & "_" & Długość & ".ipt"
ThisDoc.Document.SaveAs(Name, True)
	Else
		
	Dim Name As String
Name = ThisDoc.Path & "\" & Nr_fasady & "_" & Nr_elementu & "_" & Nr_katalogowy & "_" & Długość & "_" & Kolor & ".ipt"
ThisDoc.Document.SaveAs(Name, True)

End If
	
End If

End If

					If oChosen = "Złożenie" Then
						
'Nr_fasady = InputBox("Proszę wpisać Nr fasady:", "Potrzebne informacje", "")
Nr_fasady = "REF-1_1.1"
Nr_elementu = InputBox("Proszę wpisać Nr elementu: (Nazwa tego złożenia)", "Potrzebne informacje", "")

Dim Name As String
Name = ThisDoc.Path & "\" & Nr_fasady & "_" & Nr_elementu & ".iam"
ThisDoc.Document.SaveAs(Name, True)
End If
