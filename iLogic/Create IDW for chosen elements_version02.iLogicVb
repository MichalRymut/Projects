Sub Main()
	Dim ass As AssemblyDocument = ThisApplication.ActiveDocument
	Dim oSelSet As SelectSet = ass.SelectSet
	If oSelSet.Count = 0 Then
		MessageBox.Show("Please choose files before running the rule", "Error")
		Exit Sub
	End If
	
	'Create File Open Dialogue
	oDoc = ThisDoc.Document
	Dim oFileDlg As Inventor.FileDialog = Nothing
	InventorVb.Application.CreateFileDialog(oFileDlg)

	'3rd Party File formats:
	o1 = "3rd Party Files |*.wire; *.CATpart; *.CATproduct;*.dlv3;"
	o2 = "*.fusiondesign; *.igs; *.iges; *.jt; *.prt; *.obj; *.x_b; *.x_t; *.g; *.neu;"
	o3 = "*.prt; *.asm; *.rvt; *.3dm; *.sat; *.smt; *.stp; *.ste; *.step; *.stpz; *.stl;"
	o4 = "*.stlb; *.par; *.psm; *.asm; *.prt; *.sldprt; *.sldasm; *.model; *.session; *.exp"

	'Choose the "File Type" by uncommenting one of the options below:
	'For "ALL file Types" Comment out all lines in this section
	oFileDlg.Filter = "Drawing Files (*.dwg) (*.idw)|*.dwg; *.idw"
	oFileDlg.Filter = "Part Files (*.ipt)|*.ipt"
	oFileDlg.Filter = "Assembly Files (*.iam)|*.iam"
	oFileDlg.Filter = "XML files (*.xml)|*.xml"
	oFileDlg.Filter = o1 & o2 & o3 & o4 ' 3rd Party Files

	'Set open location using one of these 2 options below
	'oFileDlg.InitialDirectory = "C:\TEMP\"  'Hard Coded path:
	oFileDlg.InitialDirectory = ThisApplication.DesignProjectManager.ActiveDesignProject.WorkspacePath

	'Show File Open Dialogue
	oFileDlg.DialogTitle = "Choose template file"
	oFileDlg.ShowOpen()
	oTFullFileName = oFileDlg.FileName
	If oTFullFileName = "" Then 
		Return
	End If
	MessageBox.Show("You selected: " & oTFullFileName , "iLogic")
	
	
	SharedVariable(oTFullFileNameG) = oTFullFileName
	Dim Occ As ComponentOccurrence
	For Each Occ In oSelSet

		Dim OccDoc As Document = Occ.Definition.Document

		Dim oArgs As NameValueMap = ThisApplication.TransientObjects.CreateNameValueMap
		oArgs.Add("TargetDocument", OccDoc)
		iLogicVb.Automation.RunExternalRuleWithArguments(OccDoc, "Create 4 View Drawing Of Model", oArgs)
		
		
	Next
End Sub
