Dim wynik As String
Dim x As Integer
Dim z As Integer
x = 1
question = MessageBox.Show("Czy chcesz włączyć kalkulator rozstawu otworów?", "Funkcja kalkulator", MessageBoxButtons.YesNo, MessageBoxIcon.Question, MessageBoxDefaultButton.Button1)
If question = vbYes
	
i = InputBox("Wprowadź wymiar do obliczenia rozstawu otworów", "Kalkulator", "69")

While i > 300
	If x = 1
		
	 	i = i / x
	 	x = x + 1
		
		Else
	 i = i * (x - 1)
	 
	 i = i / x
	 x = x + 1
	 
 End If
	
 End While


wynik = i
	
MessageBox.Show("odległość między wystąpieniami: " & wynik & vbLf & "Ilość wystąpień: " & x, "Wynik najbliższy 300", MessageBoxButtons.OK, MessageBoxIcon.Hand, MessageBoxDefaultButton.Button1)

end if
