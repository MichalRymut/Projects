Imports System.Windows.Forms
Sub Main()
	Dim ass As AssemblyDocument = ThisApplication.ActiveDocument
	Dim oSelSet As SelectSet = ass.SelectSet
	If oSelSet.Count = 0 Then
		MessageBox.Show("Please choose files before running the rule", "Error")
		Exit Sub
	End If
	
	'Create File Open Dialogue
	
	MessageBox.Show("Choose the template for drawnings", "Warning")
	
	Dim oFileDlg As Inventor.FileDialog
	Call ThisApplication.CreateFileDialog(oFileDlg)
	oFileDlg.Filter = "Drawing Files (*.idw;*.dwg)| *.idw;*.dwg"
	oFileDlg.FilterIndex = 1
	oFileDlg.DialogTitle = "Select drawing template"
	oFileDlg.InitialDirectory = "C:\Users\Public\Documents\Autodesk\" 
	oFileDlg.InsertMode = False
	oFileDlg.MultiSelectEnabled = False
	oFileDlg.SuppressResolutionWarnings = True
	oFileDlg.CancelError = False
	oFileDlg.ShowOpen
	
	oTFullFileName = oFileDlg.FileName
	MessageBox.Show("You selected: " & oTFullFileName , "iLogic")
	
	'Choosing the folder in which to save drawnings.
	MessageBox.Show("Choose in which folder to save drawnings", "Warning")
	
	Dim Dialog = New FolderBrowserDialog()
	Dialog.SelectedPath = ExportPath
	Dialog.ShowNewFolderButton = True
	Dialog.Description = "Choose the folder in which to save idw files: "
	If DialogResult.OK = Dialog.ShowDialog() Then
		ExportPath = Dialog.SelectedPath & "\"
	Else
		Return
		
	End If
	
	' Variables that are shared with other rules
	SharedVariable("oTFullFileNameG") = oTFullFileName
	SharedVariable("SaveFolderG") = ExportPath
	
	
	' Running the rule for each chosen file
	Dim Occ As ComponentOccurrence
	For Each Occ In oSelSet

		Dim OccDoc As Document = Occ.Definition.Document

		Dim oArgs As NameValueMap = ThisApplication.TransientObjects.CreateNameValueMap
		oArgs.Add("TargetDocument", OccDoc)
		iLogicVb.Automation.RunExternalRuleWithArguments(OccDoc, "Create 4 View Drawing Of Model", oArgs)
		
		
	Next
End Sub
